DKSF-707-3-X-X-1-MIB DEFINITIONS ::= BEGIN
 
IMPORTS
        enterprises,
        MODULE-IDENTITY,
        OBJECT-TYPE,
        NOTIFICATION-TYPE 
                FROM SNMPv2-SMI 
        DisplayString
                FROM SNMPv2-TC 
        sysName        
                FROM SNMPv2-MIB ;
                
 
uniPingServerSolutionV3 MODULE-IDENTITY 
        LAST-UPDATED "201609270000Z"
        ORGANIZATION "Alentis Electronics" 
        CONTACT-INFO 
                "developers@netping.ru" 
        DESCRIPTION 
                "MIB for NetPing SMS gsm bridge" 

        REVISION "201609270000Z"
        DESCRIPTION 
                "npGsm branch updated.
                 npGsmUnparsedRxSms OID has chanded from .10 to .12.
                 npGsmSendSms renamed to npGsmSendSmsUtf8.
                 npGsmSendSmsWin1251 added." 
                
        REVISION "201605030000Z"
        DESCRIPTION 
                "added npGsmTrapUnparsedSmsWebhook trap
                for external webhook service" 
        
        REVISION "201502090000Z"
        DESCRIPTION 
                "added npGsmSendSms"                  
                
        REVISION "201403030000Z"
        DESCRIPTION 
                "initial release"   



                
        ::= { lightcom 707 }


                
lightcom OBJECT IDENTIFIER::={enterprises 25728 }


npTrapInfo OBJECT IDENTIFIER::={lightcom 90}

npTrapEmailTo OBJECT-TYPE
     SYNTAX     DisplayString
     MAX-ACCESS     read-only
     STATUS     current
     DESCRIPTION     "user-specified e-mail for NetPing Trap Forwarding Service"
     ::={npTrapInfo 1}

npWebhook OBJECT IDENTIFIER::={lightcom 95}

npWebhookUrl OBJECT-TYPE
     SYNTAX     DisplayString
     MAX-ACCESS     read-only
     STATUS     current
     DESCRIPTION     "user-specified URL for NetPing Webhook Forwarding Service"
     ::={npWebhook 31}

npGsm  OBJECT IDENTIFIER::={lightcom 3800}
npGsmInfo OBJECT IDENTIFIER::={npGsm 1}

npGsmFailed  OBJECT-TYPE 
    SYNTAX     INTEGER {
                        ok (0), 
                        failed (1),
                        fatalError (2)
                       }
    MAX-ACCESS  read-only
    STATUS     current 
    DESCRIPTION  "Firmware's GSM module status" 
    ::= { npGsmInfo 1 }   

npGsmRegistration OBJECT-TYPE 
    SYNTAX     INTEGER {
                        impossible (0), 
                        homeNetwork (1),
                        searching (2),
                        denied (3),
                        unknown (4),
                        roaming (5),
                        infoUpdate (255)
                       }
    MAX-ACCESS  read-only
    STATUS     current 
    DESCRIPTION  "Status of modem registration in GSM network (AT+CREG? result)" 
    ::= { npGsmInfo 2 } 

npGsmStrength  OBJECT-TYPE 
    SYNTAX     INTEGER (0..255)
    MAX-ACCESS  read-only
    STATUS     current 
    DESCRIPTION  "GSM signal strength.
                  0..31 = 0..100%, 
                  99 = unknown or n/a, 
                  255 = updating info" 
    ::= { npGsmInfo 3 }
    
npGsmSendSmsUtf8  OBJECT-TYPE 
    SYNTAX    DisplayString
    MAX-ACCESS  read-write
    STATUS    current 
    DESCRIPTION  "Send arbitrary SMS.
                  Format: [phone_number,phone_number,...] Message
                  One to four destination phone numbers
                  If [] and numbers omitted, mesagge will be sent to preset numbers from SMS setup
                  Cyrillic characters must be in UTF8 encoding."
    ::= { npGsmInfo 9 }

npGsmSendSmsWin1251  OBJECT-TYPE 
    SYNTAX    DisplayString
    MAX-ACCESS  read-write
    STATUS    current 
    DESCRIPTION  "Send arbitrary SMS.
                  Format: [phone_number,phone_number,...] Message
                  One to four destination phone numbers
                  If [] and numbers omitted, mesagge will be sent to preset numbers from SMS setup
                  Cyrillic characters must be in Win1251 encoding."
    ::= { npGsmInfo 10 }
    
npGsmUnparsedRxSmsFrom OBJECT-TYPE 
    SYNTAX     DisplayString
    MAX-ACCESS  accessible-for-notify
    STATUS     current 
    DESCRIPTION  "Source phone of received unparsed (unknown) Sms" 
    ::= { npGsmInfo 11 }     

npGsmUnparsedRxSms OBJECT-TYPE 
    SYNTAX     DisplayString
    MAX-ACCESS  accessible-for-notify
    STATUS     current 
    DESCRIPTION  "Received unparsed Sms with unknown starting word" 
    ::= { npGsmInfo 12 }  
    
npGsmTraps      OBJECT IDENTIFIER::={npGsm 2} 
npGsmTrapPrefix OBJECT IDENTIFIER::={npGsmTraps 0} 

npGsmTrap NOTIFICATION-TYPE
    OBJECTS { 
          npGsmFailed,
          npGsmRegistration,
          npGsmStrength
        }
    STATUS  current
    DESCRIPTION
        "GSM modem or SMS firmware problems"
    ::= { npGsmTrapPrefix 1 }
    
npGsmTrapUnparsedSms NOTIFICATION-TYPE
    OBJECTS { 
          npGsmUnparsedRxSms,
          npGsmUnparsedRxSmsFrom
        }
    STATUS  current
    DESCRIPTION
        "forwarding of SMS with wrong starting keyword"
    ::= { npGsmTrapPrefix 2 }

npGsmTrapUnparsedSmsWebhook NOTIFICATION-TYPE
    OBJECTS {
          npGsmUnparsedRxSms,
          npGsmUnparsedRxSmsFrom,
          npWebhookUrl,
          sysName
        }
    STATUS  current
    DESCRIPTION
        "Forwarding of SMS with wrong starting keyword
        to the external Webhook service.
        npGsmUnparsedRxSms encoded in UTF-8."
    ::= { npGsmTrapPrefix 3 }
    
    
npReboot OBJECT IDENTIFIER::={ lightcom 911 }   

npSoftReboot OBJECT-TYPE 
    SYNTAX     INTEGER
    MAX-ACCESS read-write 
    STATUS     current 
    DESCRIPTION  "Write 1 to reboot device after 
                  current operations completition" 
    ::= { npReboot 1 }

npResetStack OBJECT-TYPE 
    SYNTAX     INTEGER
    MAX-ACCESS read-write 
    STATUS     current 
    DESCRIPTION  "Write 1 to re-initialize network 
                  stack" 
    ::= { npReboot 2 }    

npForcedReboot OBJECT-TYPE 
    SYNTAX     INTEGER
    MAX-ACCESS read-write 
    STATUS     current 
    DESCRIPTION  "Write 1 to immediate forced reboot" 
    ::= { npReboot 3 } 
	
END
