DKSF-54-3-X-X-1 DEFINITIONS ::= BEGIN
 
IMPORTS
        enterprises,
        MODULE-IDENTITY,
        OBJECT-TYPE,
        Counter32,
        Gauge32,
        Counter64,
        Integer32,
        TimeTicks,
        NOTIFICATION-TYPE 
                FROM SNMPv2-SMI 
        TEXTUAL-CONVENTION,
        DisplayString,
        TruthValue,
        TimeStamp
                FROM SNMPv2-TC 
        snmpTraps 
                FROM SNMPv2-MIB ;
                
 
netPing4Pwr MODULE-IDENTITY 
        LAST-UPDATED "201703300000Z"  
        ORGANIZATION "Alentis Electronics" 
        CONTACT-INFO 
                "developers@netping.ru" 
        DESCRIPTION 
                "MIB for NetPing 4PWR-220/SMS remote sensing and control" 
                
        REVISION "201703300000Z"
        DESCRIPTION
                "npGsmTrap branch extended"                  
                
        REVISION "201703230000Z"
        DESCRIPTION
                "npRelayTrap branch revised"                
                
        REVISION "201612130000Z"
        DESCRIPTION
                "npIo branch added, npRelayMode values revised"

        REVISION "201611300000Z"
        DESCRIPTION
                "npRelayTrap branch added;
                 scheduleAndLogic(6) value for npRelayMode;
                 npGsmSendSms renamed to npGsmSendSmsUtf8;
                 npGsmSendSmsWin1251 added"
        
        REVISION "201512280000Z"
        DESCRIPTION
                "npRelayFlip acces corrected to read-write, npGsmSendSms description corrected"
                
        REVISION "201509080000Z"        
        DESCRIPTION                
                "npSmoke branch added, npRelHum branch extended"                   

        REVISION "201503020000Z"   
        DESCRIPTION 
                "npRelHumidity branch added
                 npGsmSendSms variable added
                 npRelayMode values redefined"  
        
        REVISION "201406190000Z"   
        DESCRIPTION 
                "Initial release"  

        ::= { lightcom 54 }


                
lightcom OBJECT IDENTIFIER::={enterprises 25728 }

npWebhook OBJECT IDENTIFIER::={lightcom 95}

npWebhookUrl OBJECT-TYPE
     SYNTAX     DisplayString
     MAX-ACCESS     read-only
     STATUS     current
     DESCRIPTION     "user-specified URL for NetPing Webhook Forwarding Service"
     ::={npWebhook 31}

npRelay OBJECT IDENTIFIER::={ lightcom 5500 }

npRelayTable       OBJECT-TYPE 
    SYNTAX     SEQUENCE OF NpRelayEntry
    MAX-ACCESS     not-accessible 
    STATUS     current 
    DESCRIPTION  "Watchdog and outlet/relay control table"     
    ::= { npRelay 5 } 

npRelayEntry     OBJECT-TYPE 
    SYNTAX     NpRelayEntry 
    MAX-ACCESS     not-accessible 
    STATUS     current 
    DESCRIPTION  "Relay/outlet table row"  
    INDEX     { npRelayN } 
    ::= { npRelayTable 1 } 

NpRelayEntry     ::= SEQUENCE { 
    npRelayN               INTEGER,
    npRelayMode            INTEGER,
    npRelayStartReset      INTEGER,
    npRelayMemo            DisplayString,
    npRelayFlip            INTEGER,    
    npRelayState           INTEGER,
    npRelayPowered         INTEGER
    } 
    
npRelayN  OBJECT-TYPE 
    SYNTAX     INTEGER  (1..4)
    MAX-ACCESS     read-only 
    STATUS     current 
    DESCRIPTION  "The N of output relay" 
    ::= { npRelayEntry 1 }
    
npRelayMode  OBJECT-TYPE
     SYNTAX     INTEGER {
                   flip(-1),
                   off(0),
                   on(1)
     }
     MAX-ACCESS     read-write
     STATUS     current
     DESCRIPTION     "Control of relay:
                     -1 - flip between on(1) and off(0)
                      0 - switch off 
                      1 - switch on"
     ::={npRelayEntry  2}
     
npRelayStartReset  OBJECT-TYPE
     SYNTAX     INTEGER
     MAX-ACCESS read-write
     STATUS     current
     DESCRIPTION     "Write 1 to start reset (switch relay off for some time)"
     ::={npRelayEntry 3}

npRelayMemo  OBJECT-TYPE
     SYNTAX     DisplayString
     MAX-ACCESS     read-only
     STATUS     current
     DESCRIPTION     "Relay memo"
     ::={npRelayEntry 6}   

npRelayFlip  OBJECT-TYPE
     SYNTAX     INTEGER {
                   flip(-1)
     }
     MAX-ACCESS     read-write
     STATUS     current
     DESCRIPTION     "Write -1 to flip between manual on and manual off states of relay"
     ::={npRelayEntry  14}     

npRelayState  OBJECT-TYPE
     SYNTAX     INTEGER {
                   off(0),
                   on(1)
     }
     MAX-ACCESS     read-only
     STATUS     current
     DESCRIPTION     "Actual relay state at the moment, 
                      regardless of source of control.
                      0 - relay is off 
                      1 - relay is on"
     ::={npRelayEntry  15}

npRelayPowered OBJECT-TYPE
     SYNTAX     INTEGER {
                   no(0),
                   yes(1)
     }
     MAX-ACCESS     read-only
     STATUS     current
     DESCRIPTION     "AC presence on output (relay operation check)
                      0 - no AC on output socket
                      1 - AC is present on oputput"
     ::={npRelayEntry  16}
     
     

npRelayTrapData OBJECT IDENTIFIER::={ npRelay 3 }

npRelayTrapN  OBJECT-TYPE 
    SYNTAX     INTEGER  (1..2)
    MAX-ACCESS     read-only 
    STATUS     current 
    DESCRIPTION  "The N of output relay" 
    ::= { npRelayTrapData 1 }
    
npRelayTrapMode  OBJECT-TYPE
     SYNTAX     INTEGER {
                   off(0),
                   on(1)
     }
     MAX-ACCESS     read-write
     STATUS     current
     DESCRIPTION     "Relay position, w/o effect of temporary switch (reset):
                      0 - off 
                      1 - on"
     ::={npRelayTrapData  2}
     
npRelayTrapMemo  OBJECT-TYPE
     SYNTAX     DisplayString
     MAX-ACCESS     read-only
     STATUS     current
     DESCRIPTION     "Relay memo"
     ::={npRelayTrapData 6}     

npRelayTrapState  OBJECT-TYPE
     SYNTAX     INTEGER {
                   off(0),
                   on(1)
     }
     MAX-ACCESS     read-only
     STATUS     current
     DESCRIPTION     "Actual relay state at the moment, 
                      0 - relay is off 
                      1 - relay is on"
     ::={npRelayTrapData  15}

npRelayTrapCmdSrc  OBJECT-TYPE
     SYNTAX     INTEGER {
                   unknown(-1),
                   webInterface(1),
                   snmp(2),
                   sms(3),
                   httpApi(4),
                   watchdog(5),
                   schedule(6),
                   logic(7)
     }
     MAX-ACCESS     read-only
     STATUS     current
     DESCRIPTION     "Source of command to switch Relay"
     ::={npRelayTrapData  18}
     
npRelayTrapDateTime  OBJECT-TYPE
     SYNTAX     DisplayString
     MAX-ACCESS     read-only
     STATUS     current
     DESCRIPTION     "Textual timestamp of event"
     ::={npRelayTrapData 19} 

npRelayTrap OBJECT IDENTIFIER::={npRelay 6}   
npRelayTrapAllEvents OBJECT IDENTIFIER::={npRelayTrap 127}

npRelayTrapAllChannels NOTIFICATION-TYPE
    OBJECTS {
        npRelayTrapN,
        npRelayTrapMode,
        npRelayTrapMemo,
        npRelayTrapState,
        npRelayTrapCmdSrc,
        npRelayTrapDateTime
        }
    STATUS  current
    DESCRIPTION
        "Status of Humidity has changed!"
    ::= { npRelayTrapAllEvents 99 }
    
npRelayTrapOff NOTIFICATION-TYPE
    OBJECTS {
        npRelayTrapN,
        npRelayTrapMode,
        npRelayTrapMemo,
        npRelayTrapState,
        npRelayTrapCmdSrc,
        npRelayTrapDateTime    
        }
    STATUS  current
    DESCRIPTION
        "Relay switched off"
    ::= { npRelayTrap 100 }
    
npRelayTrapOn NOTIFICATION-TYPE
    OBJECTS {
        npRelayTrapN,
        npRelayTrapMode,
        npRelayTrapMemo,
        npRelayTrapState,
        npRelayTrapCmdSrc,
        npRelayTrapDateTime    
        }
    STATUS  current
    DESCRIPTION
        "Relay switched on"
    ::= { npRelayTrap 101 }
    
npRelayTrapModeChange NOTIFICATION-TYPE
    OBJECTS {
        npRelayTrapN,
        npRelayTrapMode,
        npRelayTrapMemo,
        npRelayTrapState,
        npRelayTrapCmdSrc,
        npRelayTrapDateTime
        }
    STATUS  current
    DESCRIPTION
        "Relay mode changed"
    ::= { npRelayTrap 102 }

npRelayTrapReset NOTIFICATION-TYPE
    OBJECTS {
        npRelayTrapN,
        npRelayTrapMode,
        npRelayTrapMemo,
        npRelayTrapState,
        npRelayTrapCmdSrc,
        npRelayTrapDateTime    
        }
    STATUS  current
    DESCRIPTION
        "Relay reset started"
    ::= { npRelayTrap 103 }


npPwr OBJECT IDENTIFIER::={ lightcom 5800 }

npPwrTable       OBJECT-TYPE 
    SYNTAX     SEQUENCE OF NpPwrEntry
    MAX-ACCESS     not-accessible 
    STATUS     current 
    DESCRIPTION  "Watchdog and outlet/relay control table"     
    ::= { npPwr 3 } 

npPwrEntry     OBJECT-TYPE 
    SYNTAX     NpPwrEntry 
    MAX-ACCESS     not-accessible 
    STATUS     current 
    DESCRIPTION  "Watchdog control table row"  
    INDEX     { npPwrChannelN } 
    ::= { npPwrTable 1 } 

NpPwrEntry     ::= SEQUENCE { 
    npPwrChannelN               INTEGER,
    npPwrStartReset             INTEGER,
    npPwrResetsCounter          INTEGER,
    npPwrRepeatingResetsCounter INTEGER,
    npPwrMemo                   DisplayString
    } 
    
npPwrChannelN  OBJECT-TYPE 
    SYNTAX     INTEGER  (1..4)
    MAX-ACCESS     read-only 
    STATUS     current 
    DESCRIPTION  "The id of watchdog/power channel" 
    ::= { npPwrEntry 1 }
    
npPwrStartReset  OBJECT-TYPE
     SYNTAX     INTEGER (0..2)
     MAX-ACCESS read-only
     STATUS     obsolete
     DESCRIPTION     "Deprecated in current FW version: Write 1 to start forced reset.
                      On read:
                      0 - normal operation
                      1 - reset is active
                      2 - reboot pause is active or watchdog is inactive"
     ::={npPwrEntry 2}    
    
npPwrResetsCounter  OBJECT-TYPE
     SYNTAX     INTEGER (0..65535)
     MAX-ACCESS     read-write
     STATUS     current
     DESCRIPTION     "Counter of watchdog resets
                      Write 0 to clear."
     ::={npPwrEntry 4}

npPwrRepeatingResetsCounter  OBJECT-TYPE
     SYNTAX     INTEGER (0..65535)
     MAX-ACCESS read-only
     STATUS     current
     DESCRIPTION     "Counter of continous failed 
                      watchdog resets"
     ::={npPwrEntry 5}
     
npPwrMemo  OBJECT-TYPE
     SYNTAX     DisplayString
     MAX-ACCESS     read-only
     STATUS     current
     DESCRIPTION     "Watchdog channel memo"
     ::={npPwrEntry 6}     


npPwrWdogTrapData OBJECT IDENTIFIER::={ npPwr 2 }

npPwrWdogTrapN  OBJECT-TYPE 
    SYNTAX     INTEGER  (1..4)
    MAX-ACCESS     read-only 
    STATUS     current 
    DESCRIPTION  "No of Watchdog channel / output relay" 
    ::= { npPwrWdogTrapData 1 }
    
npPwrWdogTrapMemo  OBJECT-TYPE
     SYNTAX     DisplayString
     MAX-ACCESS     read-only
     STATUS     current
     DESCRIPTION     "Watchdog/Relay memo"
     ::={npPwrWdogTrapData 6} 

npPwrWdogTrapFailBitmap OBJECT-TYPE 
    SYNTAX     INTEGER
    MAX-ACCESS     read-only 
    STATUS     current 
    DESCRIPTION  "Failed adresses, bit 0 - A, bit 1 - B, bit 2 - C" 
    ::= { npPwrWdogTrapData 13 }

npPwrWdogTrap OBJECT IDENTIFIER::={npPwr 6}
    
npPwrWdogTrapReset NOTIFICATION-TYPE
    OBJECTS {
        npPwrWdogTrapN,
        npPwrWdogTrapMemo,
        npPwrWdogTrapFailBitmap    
        }
    STATUS  current
    DESCRIPTION
        "Watchdog reset started"
    ::= { npPwrWdogTrap 100 }
    
npPwrWdogTrapSuspended NOTIFICATION-TYPE
    OBJECTS {
        npPwrWdogTrapN,
        npPwrWdogTrapMemo
        }
    STATUS  current
    DESCRIPTION
        "Watchdog resets suspended because of no effect"
    ::= { npPwrWdogTrap 101 }

npPwrWdogTrapResumed NOTIFICATION-TYPE
    OBJECTS {
        npPwrWdogTrapN,
        npPwrWdogTrapMemo
        }
    STATUS  current
    DESCRIPTION
        "Watchdog normal operation resumed, successful ping after resets was suspended"
    ::= { npPwrWdogTrap 102 }
 
npThermo OBJECT IDENTIFIER::={lightcom 8800}
     
npThermoTable       OBJECT-TYPE 
    SYNTAX     SEQUENCE OF NpThermoEntry 
    MAX-ACCESS     not-accessible 
    STATUS     current 
    DESCRIPTION  "Thermo Sensors Table"     
    ::= { npThermo 1 } 

npThermoEntry       OBJECT-TYPE 
    SYNTAX     NpThermoEntry 
    MAX-ACCESS     not-accessible 
    STATUS     current 
    DESCRIPTION  "Thermo Sensors Table Row"     
    INDEX     { npThermoSensorN } 
    ::= { npThermoTable 1 } 

NpThermoEntry     ::= SEQUENCE { 
    npThermoSensorN INTEGER,
    npThermoValue   INTEGER,
    npThermoStatus  INTEGER,
    npThermoLow     INTEGER,
    npThermoHigh    INTEGER,
    npThermoMemo    DisplayString 
    } 

npThermoSensorN          OBJECT-TYPE 
    SYNTAX     INTEGER (1..8)
    MAX-ACCESS     read-only 
    STATUS     current 
    DESCRIPTION  "The id of temperature sensor, 1 to 8" 
    ::= { npThermoEntry 1 }

npThermoValue     OBJECT-TYPE 
    SYNTAX     INTEGER (-60..280)
    MAX-ACCESS     read-only 
    STATUS     current 
    DESCRIPTION  "Temperature, deg.C" 
    ::= { npThermoEntry 2 }      
     
npThermoStatus    OBJECT-TYPE 
    SYNTAX     INTEGER {
                  failed(0),
                  low(1),
                  norm(2),
                  high(3)
                }     
    MAX-ACCESS     read-only 
    STATUS     current 
    DESCRIPTION  "Temperature status (0=fault, 1=underheat, 2=normal, 3=overheat)" 
    ::= { npThermoEntry 3 }      

npThermoLow      OBJECT-TYPE 
    SYNTAX     INTEGER (-60..280)
    MAX-ACCESS     read-only 
    STATUS     current 
    DESCRIPTION  "Bottom margin of normal temperature range, deg.C" 
    ::= { npThermoEntry 4 } 

npThermoHigh     OBJECT-TYPE 
    SYNTAX     INTEGER (-60..280)
    MAX-ACCESS     read-only 
    STATUS     current 
    DESCRIPTION  "Top margin of normal temperature range, deg.C" 
    ::= { npThermoEntry 5 } 
    
npThermoMemo    OBJECT-TYPE 
    SYNTAX     DisplayString 
    MAX-ACCESS     read-only 
    STATUS     current 
    DESCRIPTION  "T channel memo" 
    ::= { npThermoEntry 6 } 
    
    
npThermoTraps      OBJECT IDENTIFIER::={npThermo 2} 
npThermoTrapPrefix OBJECT IDENTIFIER::={npThermoTraps 0} 

npThermoTrapSensorN          OBJECT-TYPE 
    SYNTAX     INTEGER (1..8)
    MAX-ACCESS     read-only 
    STATUS     current 
    DESCRIPTION  "The id of temperature sensor, 1 to 8" 
    ::= { npThermoTraps 1 }

npThermoTrapValue     OBJECT-TYPE 
    SYNTAX     INTEGER (-60..280)
    MAX-ACCESS     read-only 
    STATUS     current 
    DESCRIPTION  "Temperature, deg.C" 
    ::= { npThermoTraps 2 }      
     
npThermoTrapStatus    OBJECT-TYPE 
    SYNTAX     INTEGER {
                  failed(0),
                  low(1),
                  norm(2),
                  high(3)
                }     
    MAX-ACCESS     read-only 
    STATUS     current 
    DESCRIPTION  "Temperature status (0=fault, 1=underheat, 2=normal, 3=overheat)" 
    ::= { npThermoTraps 3 }      

npThermoTrapLow      OBJECT-TYPE 
    SYNTAX     INTEGER (-60..280)
    MAX-ACCESS     read-only 
    STATUS     current 
    DESCRIPTION  "Bottom margin of normal temperature range, deg.C" 
    ::= { npThermoTraps 4 } 

npThermoTrapHigh     OBJECT-TYPE 
    SYNTAX     INTEGER (-60..280)
    MAX-ACCESS     read-only 
    STATUS     current 
    DESCRIPTION  "Top margin of normal temperature range, deg.C" 
    ::= { npThermoTraps 5 } 
    
npThermoTrapMemo    OBJECT-TYPE 
    SYNTAX     DisplayString 
    MAX-ACCESS     read-only 
    STATUS     current 
    DESCRIPTION  "T channel memo" 
    ::= { npThermoTraps 6 } 
    
npThermoTrap NOTIFICATION-TYPE
OBJECTS { 
    npThermoTrapSensorN,
    npThermoTrapValue,
    npThermoTrapStatus,
    npThermoTrapLow,
    npThermoTrapHigh,
    npThermoTrapMemo 
        }
STATUS  current
DESCRIPTION
        "Status of Thermo sensor is changed (crossing of normal temp. range)"
::= { npThermoTrapPrefix 1 }



npIo  OBJECT IDENTIFIER::={lightcom 8900}
     
npIoTable       OBJECT-TYPE 
    SYNTAX     SEQUENCE OF NpIoEntry 
    MAX-ACCESS     not-accessible 
    STATUS     current 
    DESCRIPTION  "Digital Input/output Table"     
    ::= { npIo 1 } 

npIoEntry        OBJECT-TYPE 
    SYNTAX     NpIoEntry
    MAX-ACCESS     not-accessible 
    STATUS     current 
    DESCRIPTION  "Digital Input/output Table Row"     
    INDEX     { npIoLineN } 
    ::= { npIoTable 1 } 

NpIoEntry   ::= SEQUENCE { 
    npIoLineN    INTEGER,
    npIoLevelIn  INTEGER,
    npIoMemo     DisplayString,
    npIoPulseCounter        Counter32
    } 

npIoLineN      OBJECT-TYPE 
    SYNTAX     INTEGER (1..8)
    MAX-ACCESS     read-only 
    STATUS     current 
    DESCRIPTION  "Number of IO line, from 1 to max supported" 
    ::= { npIoEntry 1 }

npIoLevelIn    OBJECT-TYPE 
    SYNTAX     INTEGER (0..1)
    MAX-ACCESS     read-only 
    STATUS     current 
    DESCRIPTION  "Input level, 0 or 1" 
    ::= { npIoEntry 2 }
    
npIoMemo    OBJECT-TYPE 
    SYNTAX     DisplayString 
    MAX-ACCESS     read-only 
    STATUS     current 
    DESCRIPTION  "IO line memo" 
    ::= { npIoEntry 6 }    

npIoPulseCounter   OBJECT-TYPE 
    SYNTAX     Counter32
    MAX-ACCESS     read-write 
    STATUS     current 
    DESCRIPTION  "Pulse Counter on IO input line (counts positive fronts)
                  Write 0 to reset." 
    ::= { npIoEntry 9 }     


npIoTraps      OBJECT IDENTIFIER::={npIo 2} 
npIoTrapPrefix OBJECT IDENTIFIER::={npIoTraps 0} 

npIoTrapLineN OBJECT-TYPE 
    SYNTAX     INTEGER (1..2)
    MAX-ACCESS     read-only 
    STATUS     current 
    DESCRIPTION  "Trap data, Number of IO line" 
    ::= { npIoTraps 1 }

npIoTrapLevelIn OBJECT-TYPE 
    SYNTAX     INTEGER (0..1)
    MAX-ACCESS     read-only 
    STATUS     current 
    DESCRIPTION  "Trap data, new Input level, 0 or 1" 
    ::= { npIoTraps 2 }

npIoTrapMemo OBJECT-TYPE 
    SYNTAX     DisplayString 
    MAX-ACCESS     read-only 
    STATUS     current 
    DESCRIPTION  "Trap data, IO line memo" 
    ::= { npIoTraps 6 }
    
npIoTrapLevelLegend OBJECT-TYPE 
    SYNTAX     DisplayString 
    MAX-ACCESS     read-only 
    STATUS     current 
    DESCRIPTION  "Legend for current logic level on the IO line" 
    ::= { npIoTraps 7 }    
    
npIoTrap NOTIFICATION-TYPE
    OBJECTS { 
          npIoTrapLineN,
          npIoTrapLevelIn,
          npIoTrapMemo,
          npIoTrapLevelLegend
        }
    STATUS  current
    DESCRIPTION
        "Input state of IO line is changed"
    ::= { npIoTrapPrefix 1 }



npSmoke OBJECT IDENTIFIER::={lightcom 8200}
     
npSmokeTable       OBJECT-TYPE 
    SYNTAX     SEQUENCE OF NpSmokeEntry 
    MAX-ACCESS     not-accessible 
    STATUS     current 
    DESCRIPTION  "Smoke Sensors Table"     
    ::= { npSmoke 1 } 

npSmokeEntry       OBJECT-TYPE 
    SYNTAX     NpSmokeEntry 
    MAX-ACCESS     not-accessible 
    STATUS     current 
    DESCRIPTION  "Smoke Sensors Table Row"     
    INDEX     { npSmokeSensorN } 
    ::= { npSmokeTable 1 } 

NpSmokeEntry     ::= SEQUENCE { 
    npSmokeSensorN INTEGER,
    npSmokeStatus  INTEGER,
	npSmokePower   INTEGER,
	npSmokeReset   INTEGER,
    npSmokeMemo    DisplayString 
    } 

npSmokeSensorN          OBJECT-TYPE 
    SYNTAX     INTEGER (1..4)
    MAX-ACCESS     read-only 
    STATUS     current 
    DESCRIPTION  "The id of 1Wire Smoke sensor, 1 to 4" 
    ::= { npSmokeEntry 1 }	 

npSmokeStatus          OBJECT-TYPE 
    SYNTAX     INTEGER {
	                ok(0),
					alarm(1),
					off(4),
					failed(5)
	}
    MAX-ACCESS     read-only 
    STATUS     current 
    DESCRIPTION  "Status of Smoke sensor" 
    ::= { npSmokeEntry 2 }

npSmokePower          OBJECT-TYPE 
    SYNTAX     INTEGER {
	                off(0),
					on(1)
	}
    MAX-ACCESS     read-write 
    STATUS     current 
    DESCRIPTION  "Controls power on Smoke sensor current loop" 
    ::= { npSmokeEntry 3 }

npSmokeReset          OBJECT-TYPE 
    SYNTAX     INTEGER
    MAX-ACCESS     read-write 
    STATUS     current 
    DESCRIPTION  "Write 1 to switch off for approx. 10s to reset sensor" 
    ::= { npSmokeEntry 4 }	

npSmokeMemo    OBJECT-TYPE 
    SYNTAX     DisplayString 
    MAX-ACCESS     read-only 
    STATUS     current 
    DESCRIPTION  "Smoke sensor memo" 
    ::= { npSmokeEntry 6 } 	
 
   
npSmokeTraps      OBJECT IDENTIFIER::={npSmoke 2} 
npSmokeTrapPrefix OBJECT IDENTIFIER::={npSmokeTraps 0} 

npSmokeTrapSensorN          OBJECT-TYPE 
    SYNTAX     INTEGER (1..4)
    MAX-ACCESS     read-only 
    STATUS     current 
    DESCRIPTION  "The id of 1Wire Smoke sensor, 1 to 4" 
    ::= { npSmokeTraps 1 }

npSmokeTrapStatus    OBJECT-TYPE 
    SYNTAX     INTEGER {
	                ok(0),
					alarm(1),
					off(4),
					failed(5)
	}     
    MAX-ACCESS     read-only 
    STATUS     current 
    DESCRIPTION  "New status of Smoke sensor" 
    ::= { npSmokeTraps 2 }   

npSmokeTrapMemo    OBJECT-TYPE 
    SYNTAX     DisplayString 
    MAX-ACCESS     read-only 
    STATUS     current 
    DESCRIPTION  "Smoke sensor memo" 
    ::= { npSmokeTraps 6 } 
    
npSmokeTrap NOTIFICATION-TYPE
OBJECTS { 
    npSmokeTrapSensorN,
    npSmokeTrapStatus,
    npSmokeTrapMemo 
        }
STATUS  current
DESCRIPTION
        "Status of 1W Smoke sensor has changed"
::= { npSmokeTrapPrefix 1 }



npRelHumidity OBJECT IDENTIFIER::={lightcom 8400}

npRelHumTable       OBJECT-TYPE 
    SYNTAX     SEQUENCE OF NpRelHumEntry 
    MAX-ACCESS     not-accessible 
    STATUS     current 
    DESCRIPTION  "Humidity+Temperature Sensors Table"     
    ::= { npRelHumidity 1 } 

npRelHumEntry       OBJECT-TYPE 
    SYNTAX     NpRelHumEntry 
    MAX-ACCESS     not-accessible 
    STATUS     current 
    DESCRIPTION  "Humidity+Temperature Sensors Table Row"     
    INDEX     { npRelHumN } 
    ::= { npRelHumTable 1 } 
    
NpRelHumEntry     ::= SEQUENCE { 
    npRelHumN             INTEGER,
    npRelHumValue         INTEGER,
    npRelHumStatus        INTEGER,
    npRelHumTempValue     INTEGER,
    npRelHumTempStatus    INTEGER, 
    npRelHumMemo          DisplayString,
    npRelHumSafeRangeHigh INTEGER,
    npRelHumSafeRangeLow  INTEGER,
    npRelHumTempSafeRangeHigh INTEGER,
    npRelHumTempSafeRangeLow  INTEGER
    }

npRelHumN          OBJECT-TYPE 
    SYNTAX     INTEGER (1..4)
    MAX-ACCESS     read-only 
    STATUS     current 
    DESCRIPTION  "Index of Humidity+Temperature sensor, 1 to max supported" 
    ::= { npRelHumEntry 1 }    

npRelHumValue    OBJECT-TYPE 
    SYNTAX     INTEGER (0..100)
    MAX-ACCESS     read-only 
    STATUS     current 
    DESCRIPTION  "Relative humidity value, %" 
    ::= { npRelHumEntry 2 } 
    
npRelHumStatus     OBJECT-TYPE 
    SYNTAX     INTEGER {
                  sensorFailed(0),
                  belowSafeRange(1),
                  inSafeRange(2),
                  aboveSafeRange(3)
                }  
    MAX-ACCESS     read-only 
    STATUS     current 
    DESCRIPTION  "Status of Relative Humiduty" 
    ::= { npRelHumEntry 3 }     
    
npRelHumTempValue     OBJECT-TYPE 
    SYNTAX     INTEGER (-60..200)
    MAX-ACCESS     read-only 
    STATUS     current 
    DESCRIPTION  "Sensor temperature, deg.C" 
    ::= { npRelHumEntry 4 }     

npRelHumTempStatus     OBJECT-TYPE 
    SYNTAX     INTEGER {
                  sensorFailed(0),
                  belowSafeRange(1),
                  inSafeRange(2),
                  aboveSafeRange(3)
                }  
    MAX-ACCESS     read-only 
    STATUS     current 
    DESCRIPTION  "Status of Relative Humiduty" 
    ::= { npRelHumEntry 5 } 

npRelHumMemo    OBJECT-TYPE 
    SYNTAX     DisplayString 
    MAX-ACCESS     read-only 
    STATUS     current 
    DESCRIPTION  "Sensor Memo/Location" 
    ::= { npRelHumEntry 6 }    
	
npRelHumSafeRangeHigh    OBJECT-TYPE 
    SYNTAX     INTEGER (0..100)
    MAX-ACCESS     read-only 
    STATUS     current 
    DESCRIPTION  "Relative Humidity safe range, top margin, %RH" 
    ::= { npRelHumEntry 7 } 	
	
npRelHumSafeRangeLow    OBJECT-TYPE 
    SYNTAX     INTEGER (0..100)
    MAX-ACCESS     read-only 
    STATUS     current 
    DESCRIPTION  "Relative Humidity safe range, bottom margin, %RH" 
    ::= { npRelHumEntry 8 } 		

npRelHumTempSafeRangeHigh    OBJECT-TYPE 
    SYNTAX     INTEGER (-55..150)
    MAX-ACCESS     read-only 
    STATUS     current 
    DESCRIPTION  "Temperature safe range, top margin, deg.C" 
    ::= { npRelHumEntry 9 } 	
	
npRelHumTempSafeRangeLow    OBJECT-TYPE 
    SYNTAX     INTEGER (-55..150)
    MAX-ACCESS     read-only 
    STATUS     current 
    DESCRIPTION  "Temperature safe range, bottom margin, deg.C" 
    ::= { npRelHumEntry 10 }

npRelHumTrapData OBJECT IDENTIFIER::={npRelHumidity 3}

npRelHumTrapDataN          OBJECT-TYPE 
    SYNTAX     INTEGER (1..4)
    MAX-ACCESS     read-only 
    STATUS     current 
    DESCRIPTION  "Index of Humidity+Temperature sensor, 1 to max supported" 
    ::= { npRelHumTrapData 1 }    

npRelHumTrapDataValue     OBJECT-TYPE 
    SYNTAX     INTEGER
    MAX-ACCESS     read-only 
    STATUS     current 
    DESCRIPTION  "Sensor humidity, %RH, or temperature, deg.C" 
    ::= { npRelHumTrapData 2 }

npRelHumTrapDataStatus     OBJECT-TYPE 
    SYNTAX     INTEGER {
                  sensorFailed(0),
                  belowSafeRange(1),
                  inSafeRange(2),
                  aboveSafeRange(3)
                }  
    MAX-ACCESS     read-only 
    STATUS     current 
    DESCRIPTION  "Status of humidity or temperature" 
    ::= { npRelHumTrapData 4 } 

npRelHumTrapDataMemo    OBJECT-TYPE 
    SYNTAX     DisplayString 
    MAX-ACCESS     read-only 
    STATUS     current 
    DESCRIPTION  "Sensor Memo/Location" 
    ::= { npRelHumTrapData 6 }    
	
npRelHumTrapDataSafeRangeHigh    OBJECT-TYPE 
    SYNTAX     INTEGER
    MAX-ACCESS     read-only 
    STATUS     current 
    DESCRIPTION  "Relative Humidity safe range, top margin, %RH or deg.C" 
    ::= { npRelHumTrapData 7 } 	
	
npRelHumTrapDataSafeRangeLow    OBJECT-TYPE 
    SYNTAX     INTEGER
    MAX-ACCESS     read-only 
    STATUS     current 
    DESCRIPTION  "Relative Humidity safe range, bottom margin, %RH or deg.C" 
    ::= { npRelHumTrapData 8 } 	

npRelHumTrap OBJECT IDENTIFIER::={npRelHumidity 6}   
npRelHumTrapAllEvents OBJECT IDENTIFIER::={npRelHumTrap 127}
npRelHumTrapTemp OBJECT IDENTIFIER::={npRelHumidity 7}  
npRelHumTrapTempAllEvents OBJECT IDENTIFIER::={npRelHumTrapTemp 127}

npRelHumTrapAllChannels NOTIFICATION-TYPE
    OBJECTS {
  npRelHumTrapDataN,    
	npRelHumTrapDataStatus,
  npRelHumTrapDataValue,
  npRelHumTrapDataMemo,
	npRelHumTrapDataSafeRangeHigh,
	npRelHumTrapDataSafeRangeLow
        }
    STATUS  current
    DESCRIPTION
        "Status of Humidity has changed!"
    ::= { npRelHumTrapAllEvents 99 }
    
npRelHumTrapAboveSafe NOTIFICATION-TYPE
    OBJECTS {
  npRelHumTrapDataN,    
	npRelHumTrapDataStatus,
  npRelHumTrapDataValue,
  npRelHumTrapDataMemo,
	npRelHumTrapDataSafeRangeHigh,
	npRelHumTrapDataSafeRangeLow
        }
    STATUS  current
    DESCRIPTION
        "Humidity above the Safe range"
    ::= { npRelHumTrap 103 }

npRelHumTrapSafe NOTIFICATION-TYPE
    OBJECTS {
  npRelHumTrapDataN,    
	npRelHumTrapDataStatus,
  npRelHumTrapDataValue,
  npRelHumTrapDataMemo,
	npRelHumTrapDataSafeRangeHigh,
	npRelHumTrapDataSafeRangeLow
        }
    STATUS  current
    DESCRIPTION
        "Humidity in the Safe range"
    ::= { npRelHumTrap 102 }

npRelHumTrapBelowSafe NOTIFICATION-TYPE
    OBJECTS {
  npRelHumTrapDataN,    
	npRelHumTrapDataStatus,
  npRelHumTrapDataValue,
  npRelHumTrapDataMemo,
	npRelHumTrapDataSafeRangeHigh,
	npRelHumTrapDataSafeRangeLow
        }
    STATUS  current
    DESCRIPTION
        "Humidity below the Safe range"
    ::= { npRelHumTrap 101 }

npRelHumTrapFail NOTIFICATION-TYPE
    OBJECTS {
  npRelHumTrapDataN,    
	npRelHumTrapDataStatus,
  npRelHumTrapDataValue,
  npRelHumTrapDataMemo,
	npRelHumTrapDataSafeRangeHigh,
	npRelHumTrapDataSafeRangeLow
        }
    STATUS  current
    DESCRIPTION
        "Rel.Humidity sensor failed!"
    ::= { npRelHumTrap 100 }      

npRelHumTrapTempAllChannels NOTIFICATION-TYPE
    OBJECTS {
  npRelHumTrapDataN,    
	npRelHumTrapDataStatus,
  npRelHumTrapDataValue,
  npRelHumTrapDataMemo,
	npRelHumTrapDataSafeRangeHigh,
	npRelHumTrapDataSafeRangeLow
        }
    STATUS  current
    DESCRIPTION
        "Status of Temperature has changed!"
    ::= { npRelHumTrapTempAllEvents 99 }

npRelHumTrapTempAboveSafe NOTIFICATION-TYPE
    OBJECTS {
  npRelHumTrapDataN,    
	npRelHumTrapDataStatus,
  npRelHumTrapDataValue,
  npRelHumTrapDataMemo,
	npRelHumTrapDataSafeRangeHigh,
	npRelHumTrapDataSafeRangeLow
        }
    STATUS  current
    DESCRIPTION
        "Temperature above the Safe range"
    ::= { npRelHumTrapTemp 103 }

npRelHumTrapTempSafe NOTIFICATION-TYPE
    OBJECTS {
  npRelHumTrapDataN,    
	npRelHumTrapDataStatus,
  npRelHumTrapDataValue,
  npRelHumTrapDataMemo,
	npRelHumTrapDataSafeRangeHigh,
	npRelHumTrapDataSafeRangeLow
        }
    STATUS  current
    DESCRIPTION
        "Temperature in the Safe range"
    ::= { npRelHumTrapTemp 102 }

npRelHumTrapTempBelowSafe NOTIFICATION-TYPE
    OBJECTS {
  npRelHumTrapDataN,    
	npRelHumTrapDataStatus,
  npRelHumTrapDataValue,
  npRelHumTrapDataMemo,
	npRelHumTrapDataSafeRangeHigh,
	npRelHumTrapDataSafeRangeLow
        }
    STATUS  current
    DESCRIPTION
        "Temperature below the Safe range"
    ::= { npRelHumTrapTemp 101 }
    
npRelHumTrapTempFail NOTIFICATION-TYPE
    OBJECTS {
  npRelHumTrapDataN,    
	npRelHumTrapDataStatus,
  npRelHumTrapDataValue,
  npRelHumTrapDataMemo,
	npRelHumTrapDataSafeRangeHigh,
	npRelHumTrapDataSafeRangeLow
        }
    STATUS  current
    DESCRIPTION
        "Sensor failed!"
    ::= { npRelHumTrapTemp 100 }


npGsm  OBJECT IDENTIFIER::={lightcom 3800}
npGsmInfo OBJECT IDENTIFIER::={npGsm 1}

npGsmFailed  OBJECT-TYPE 
    SYNTAX     INTEGER {
                        ok (0), 
                        failed (1),
                        fatalError (2)
                       }
    MAX-ACCESS  read-only
    STATUS     current 
    DESCRIPTION  "Firmware's GSM module status" 
    ::= { npGsmInfo 1 }   

npGsmRegistration OBJECT-TYPE 
    SYNTAX     INTEGER {
                        impossible (0), 
                        homeNetwork (1),
                        searching (2),
                        denied (3),
                        unknown (4),
                        roaming (5),
                        infoUpdate (255)
                       }
    MAX-ACCESS  read-only
    STATUS     current 
    DESCRIPTION  "Status of modem registration in GSM network (AT+CREG? result)" 
    ::= { npGsmInfo 2 } 

npGsmStrength  OBJECT-TYPE 
    SYNTAX     INTEGER (0..255)
    MAX-ACCESS  read-only
    STATUS     current 
    DESCRIPTION  "GSM signal strength.
                  0..31 = 0..100%, 
                  99 = unknown or n/a, 
                  255 = updating info" 
    ::= { npGsmInfo 3 }

npGsmSendSmsUtf8  OBJECT-TYPE 
    SYNTAX    DisplayString
    MAX-ACCESS  read-write
    STATUS    current 
    DESCRIPTION  "Send arbitrary SMS.
                  Format: [phone_number,phone_number,...] Message
                  One to four destination phone numbers
                  If [] and numbers omitted, mesagge will be sent to preset numbers from SMS setup
                  Cyrillic characters must be in UTF8 encoding."
    ::= { npGsmInfo 9 }

npGsmSendSmsWin1251  OBJECT-TYPE 
    SYNTAX    DisplayString
    MAX-ACCESS  read-write
    STATUS    current 
    DESCRIPTION  "Send arbitrary SMS.
                  Format: [phone_number,phone_number,...] Message
                  One to four destination phone numbers
                  If [] and numbers omitted, mesagge will be sent to preset numbers from SMS setup
                  Cyrillic characters must be in Win1251 encoding."
    ::= { npGsmInfo 10 }
    
npGsmUnparsedRxSmsFrom OBJECT-TYPE 
    SYNTAX     DisplayString
    MAX-ACCESS  accessible-for-notify
    STATUS     current 
    DESCRIPTION  "Source phone of received unparsed (unknown) Sms" 
    ::= { npGsmInfo 11 }     

npGsmUnparsedRxSms OBJECT-TYPE 
    SYNTAX     DisplayString
    MAX-ACCESS  accessible-for-notify
    STATUS     current 
    DESCRIPTION  "Received unparsed Sms with unknown starting word" 
    ::= { npGsmInfo 12 }  
    
npGsmTraps      OBJECT IDENTIFIER::={npGsm 2} 
npGsmTrapPrefix OBJECT IDENTIFIER::={npGsmTraps 0} 

npGsmTrap NOTIFICATION-TYPE
    OBJECTS { 
          npGsmFailed,
          npGsmRegistration,
          npGsmStrength
        }
    STATUS  current
    DESCRIPTION
        "GSM modem or SMS firmware problems"
    ::= { npGsmTrapPrefix 1 }
    
npGsmTrapUnparsedSms NOTIFICATION-TYPE
    OBJECTS { 
          npGsmUnparsedRxSms,
          npGsmUnparsedRxSmsFrom
        }
    STATUS  current
    DESCRIPTION
        "forwarding of SMS with wrong starting keyword"
    ::= { npGsmTrapPrefix 2 }

npGsmTrapUnparsedSmsWebhook NOTIFICATION-TYPE
    OBJECTS {
          npGsmUnparsedRxSms,
          npGsmUnparsedRxSmsFrom,
          npWebhookUrl,
          sysName
        }
    STATUS  current
    DESCRIPTION
        "Forwarding of SMS with wrong starting keyword
        to the external Webhook service.
        npGsmUnparsedRxSms encoded in UTF-8."
    ::= { npGsmTrapPrefix 3 }

npBattery OBJECT IDENTIFIER::={ lightcom 3900 }
npBatteryInfo OBJECT IDENTIFIER::={npBattery 1}

npBatteryPok   OBJECT-TYPE 
    SYNTAX     INTEGER {
                  batteryPower  (0),
                  externalPower (1)
                       }
    MAX-ACCESS read-only 
    STATUS     current 
    DESCRIPTION  "Power source" 
    ::= { npBatteryInfo 1 }   
    
npBatteryLevel   OBJECT-TYPE 
    SYNTAX     INTEGER (0..100)
    MAX-ACCESS read-only 
    STATUS     current 
    DESCRIPTION  "Battery charge, approximate value, in percent.
                  Valid only if npBatteryPok = 0" 
    ::= { npBatteryInfo 2 }  
    
npBatteryChg   OBJECT-TYPE 
    SYNTAX     INTEGER {
                  batteryChargingSuspended (0),
                  batteryFastCharging (1)
                    }
    MAX-ACCESS read-only 
    STATUS     current 
    DESCRIPTION  "Battery chargeing status.
                  0 if charging suspended or battery is full,
                  1 while LiPo fast charging." 
    ::= { npBatteryInfo 3 }


npPowerMon  OBJECT IDENTIFIER::={ lightcom 2400 }

npPowerMonTable       OBJECT-TYPE 
    SYNTAX     SEQUENCE OF NpPowerMonEntry 
    MAX-ACCESS     not-accessible 
    STATUS     current 
    DESCRIPTION  "AC Quality Monitoring Table"     
    ::= { npPowerMon 1 } 

npPowerMonEntry       OBJECT-TYPE 
    SYNTAX     NpPowerMonEntry 
    MAX-ACCESS     not-accessible 
    STATUS     current 
    DESCRIPTION  "AC Quality Monitoring Table Row"     
    INDEX     { npPowerMonN } 
    ::= { npPowerMonTable 1 } 
    
NpPowerMonEntry     ::= SEQUENCE { 
    npPowerMonN          INTEGER,
    npPowerMonCountUV1   Counter32,
    npPowerMonCountOV1   Counter32, 
    npPowerMonCountUV2   Counter32,
    npPowerMonCountOV2   Counter32,  
    npPowerMonCountUV3   Counter32
    }

npPowerMonN          OBJECT-TYPE 
    SYNTAX     INTEGER (1..4)
    MAX-ACCESS     read-only 
    STATUS     current 
    DESCRIPTION  "Index of AC Quality Monitoring sensor, 1 to max supported" 
    ::= { npPowerMonEntry 1 }    

npPowerMonCountUV1    OBJECT-TYPE 
    SYNTAX     Counter32
    MAX-ACCESS     read-only 
    STATUS     current 
    DESCRIPTION  "Counter of short voltage sags (dips)" 
    ::= { npPowerMonEntry 2 } 
    
npPowerMonCountOV1    OBJECT-TYPE 
    SYNTAX     Counter32
    MAX-ACCESS     read-only 
    STATUS     current 
    DESCRIPTION  "Counter of short voltage swells" 
    ::= { npPowerMonEntry 3 } 
    
npPowerMonCountUV2    OBJECT-TYPE 
    SYNTAX     Counter32
    MAX-ACCESS     read-only 
    STATUS     current 
    DESCRIPTION  "Counter of long voltage sags (dips)" 
    ::= { npPowerMonEntry 4 } 
    
npPowerMonCountOV2    OBJECT-TYPE 
    SYNTAX     Counter32
    MAX-ACCESS     read-only 
    STATUS     current 
    DESCRIPTION  "Counter of long voltage swells" 
    ::= { npPowerMonEntry 5 }     
    
npPowerMonCountUV3    OBJECT-TYPE 
    SYNTAX     Counter32
    MAX-ACCESS     read-only 
    STATUS     current 
    DESCRIPTION  "Counter of voltage blackouts" 
    ::= { npPowerMonEntry 6 } 
    
    
    
npReboot OBJECT IDENTIFIER::={ lightcom 911 }   

npSoftReboot OBJECT-TYPE 
    SYNTAX     INTEGER
    MAX-ACCESS read-write 
    STATUS     current 
    DESCRIPTION  "Write 1 to reboot device after 
                  current operations completition" 
    ::= { npReboot 1 }

npResetStack OBJECT-TYPE 
    SYNTAX     INTEGER
    MAX-ACCESS read-write 
    STATUS     current 
    DESCRIPTION  "Write 1 to re-initialize network 
                  stack" 
    ::= { npReboot 2 }    

npForcedReboot OBJECT-TYPE 
    SYNTAX     INTEGER
    MAX-ACCESS read-write 
    STATUS     current 
    DESCRIPTION  "Write 1 to immediate forced reboot" 
    ::= { npReboot 3 } 
	
END
